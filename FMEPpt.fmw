FME workspace FMEPpt.fmw
Title: We love ppt
Description: En övergripande beskrivning av skriptet 2025

Parameters:
- INFO =   # Blandad information. Det är viktigt att denna är med :-)
- WAIT = 1   # Wait x sec
- TITLE = FME   # The Title
- AreaOfInterest = {"type":"polygon","rings":[[[130701.04909305644,6175501.390244796],[130672.5735042545,6175571.106341518],[130684.35650651738,6175716.430036094],[130797.27694486994,6175678.135278739],[130803.16844600138,6175654.569274213],[130881.72179442055,6175580.92551007],[130924.9261360511,6175531.829667308],[130874.84837643387,6175499.426411086],[130701.04909305644,6175501.390244796]]],"_ring":0,"spatialReference":{"wkid":3008,"latestWkid":3008}}   # Hidden

Note: Sätt Namn och Overview under 'Workspace Parameters' --> 'General' --> 'Name' och 'Overview'
Note: Skapa 'User parameters' för ditt skript. AreaOfInterset är default i Widgeten för geojson för beställninghen
Creator
    GEOMTYPE = Geometry Object
    NUM = 1
    CREATED -> GeometryReplacer
Note: Gör om 'User Parameter' 'AreaOfInterest' geojson till en feature
GeometryReplacer
    KIND = ESRIJSON
    REMOVE_ATTRIBUTE = No
    SOURCE = $(AreaOfInterest)
    KIND_LONG = Esri JSON
    -> Decelerator
    -> AreaCalculator
Note: Flera skript kan publiceras i samma Repository.
Note: Döp om FeatureWritern för att få bättre namn på katalog i export-zippen
Decelerator
    DECEL_LOOKUP = PERFEATDELAY
    DELAY = $(WAIT)
    DECEL_TYPE = Per Feature Delay
    -> geojson [Created]
AreaCalculator
    AREA_ATTR = _area
    AREA_TYPE = Plane Area
    MULT = 1
    -> PowerPointStyler
    -> AttributeRounder
PowerPointStyler
    PARAMETER_SETUP = powerpoint_title_text_Title_Slide[$(TITLE)[powerpoint_subtitle_text[FME Användardag[powerpoint_title_text[$(TITLE)
    SLIDE_TYPE = Title Slide
    powerpoint_slide_order = Automatic
    powerpoint_sub_order = Automatic
    powerpoint_subtitle_text = FME Användardag
    powerpoint_title_text = $(TITLE)
    powerpoint_title_text_Title_Slide = $(TITLE)
    -> FMEAnvandardag [Created]
AttributeRounder
    PLACES = 3
    ROUND_TYPE_TCL = round
    SRC_ATTRS = _area
    ROUND_TYPE = Nearest
    -> PowerPointStyler_2
PowerPointStyler_2
    PARAMETER_SETUP = powerpoint_slide_subtype_Map_Slide[WithTitle[powerpoint_title_text_Chart_Slide[Area: @Value(_area)[powerpoint_caption_text[<Unused>[LABEL_GROUP[[powerpoint_map_label[[fme_powerpoint_font_data_Map_Slide[[powerpoint_font_color_Map_Slide[[powerpoint_label_wrap[No[FILL_GROUP[[powerpoint_map_fill_pattern[[powerpoint_map_fill_fore_color[[powerpoint_map_fill_back_color[[BORDER_GROUP[[powerpoint_map_border_style[[powerpoint_map_border_width[1[powerpoint_map_border_color[[HYPERLINK_GROUP_Map_Slide[[powerpoint_hyperlink_Map_Slide[[powerpoint_merge_features_Map_Slide[No[powerpoint_merge_id_Map_Slide[<Unused>[HYPERLINK_GROUP[[fme_powerpoint_font_data[[powerpoint_font_color[[powerpoint_hyperlink[[powerpoint_merge_features[No[powerpoint_slide_subtype[WithTitle[powerpoint_title_text[Area: @Value(_area)
    SLIDE_TYPE = Map Slide
    powerpoint_label_wrap = No
    powerpoint_map_border_width = 1
    powerpoint_merge_features = No
    powerpoint_merge_features_Map_Slide = No
    powerpoint_slide_order = Automatic
    powerpoint_slide_subtype = WithTitle
    powerpoint_slide_subtype_Map_Slide = WithTitle
    powerpoint_sub_order = Automatic
    powerpoint_title_text = Area: @Value(_area)
    powerpoint_title_text_Chart_Slide = Area: @Value(_area)
    -> FMEAnvandardag [Output]

Bookmark: FeatureWriters
geojson: FeatureWriter
    DATASET = area.geojson
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written
FMEAnvandardag: FeatureWriter
    DATASET = ThePoverpoint.ppt
    DATASET_ATTR = _dataset
    FEATURE_TYPE_LIST_ATTR = _feature_types
    FORMAT = POWERPOINT
    TOTAL_FEATURES_WRITTEN_ATTR = _total_features_written
